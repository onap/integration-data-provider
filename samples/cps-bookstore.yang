module stores {
    yang-version 1.1;
    namespace "org:onap:ccsdk:sample";

    prefix book-store;

    revision "2020-09-15" {
        description
          "Sample Model";
    }
    container shops {

        container bookstore {

            leaf bookstore-name {
                type string;
            }

            leaf name {
                type string;
            }

            list categories {

                key "code";

                leaf code {
                    type uint16;
                }

                leaf name {
                    type string;
                }

                leaf numberOfBooks {
                    type uint16;
                }

                container books {

                    list book {
                        key title;

                        leaf title {
                            type string;
                        }
                        leaf price {
                            type uint16;
                        }
                        leaf-list label {
                            type string;
                        }
                        leaf-list edition {
                            type string;
                        }
                    }
                }
            }
        }
    }
}
